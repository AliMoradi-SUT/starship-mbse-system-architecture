# Communication Requirements

## REQ-SYS-01: Link availability (Functional)
Communication shall maintain at least one active downlink path (relay or direct-to-ground) providing telemetry connectivity across every mission phase, including atmospheric entry.

## REQ-SYS-02: Downlink throughput budget (Functional)
Combined downlink capacity across both paths shall meet the aggregate data rate required for real-time telemetry, video, and recorded-data playback within the mission's data budget.

## REQ-SYS-03: Communication dry mass budget (Functional)
Total Communication subsystem dry mass (both terminals, C&DH, ground interface) shall not exceed the mass allocation set by the vehicle-level mass budget.

## REQ-LNK-01: Relay link margin (Functional)
The relay link shall maintain positive link margin under worst-case pointing/attitude conditions across the constellation elevation-angle range used for acquisition.

## REQ-LNK-02: Direct-to-ground link margin (Functional)
The direct-to-ground link shall maintain positive link margin across the vehicle's expected range and attitude envelope relative to ground stations.

## REQ-LNK-03: Regulatory EIRP / PFD compliance (Functional)
Both downlink paths shall operate within FCC-authorized EIRP and power-flux-density limits for their licensed frequency bands.

## REQ-RDN-01: Reentry blackout handoff (Functional)
Link management shall detect direct-to-ground link degradation during atmospheric entry and hand primary downlink responsibility to the relay path without commanded intervention.

## REQ-RDN-02: No single point of failure across paths (Functional)
Loss of either the relay path or the direct-to-ground path alone shall not result in loss of all downlink or uplink capability for more than a defined maximum outage duration.

## REQ-RDN-03: Path selection determinism (Functional)
Link management shall select a single authoritative uplink source when both paths are simultaneously receiving, preventing conflicting or duplicate command execution.

## REQ-CDH-01: Telemetry aggregation completeness (Functional)
The telemetry aggregator shall incorporate telemetry from every subsystem interface presented to Communication — including EngineTelemetry and TankTelemetry — into the downlink stream without silent data loss.

## REQ-CDH-02: Onboard data recording depth (Functional)
The data recorder shall buffer telemetry and video for at least the expected worst-case continuous coverage-gap duration without data loss.

## REQ-CDH-03: Command routing latency (Functional)
Commands verified by the command decoder & router shall be delivered to GNC or Safety and Fault Management within a defined maximum latency of receipt.

## REQ-CDH-04: Video bandwidth allocation (Functional)
Video capture & encoding shall constrain its output bit rate so that video does not starve telemetry bandwidth on either downlink path.

## REQ-SEC-01: Command authentication (Functional)
The command decoder & router shall reject any uplinked command that fails authentication before routing it to GNC or Safety and Fault Management.

## REQ-SEC-02: Replay protection (Functional)
The command decoder & router shall reject a previously-executed command received a second time, preventing unintended re-execution from a corrupted or repeated link.

## REQ-GSE-01: Pre-launch checkout throughput (Functional)
The ground data interface shall support the data rate required for pre-launch subsystem checkout and telemetry playback verification within the countdown timeline.

## REQ-GSE-02: Quick-disconnect release (Functional)
The vehicle-side data QD panel shall cleanly disconnect at or before liftoff without damaging vehicle-side wiring or connectors.

## REQ-CTL-01: Link health reporting (Functional)
Communication shall report link status — active path, signal quality, handoff events — to Safety and Fault Management within a defined response time of a change in state.

## REQ-CTL-02: Autonomous terminal fault isolation (Functional)
A failed antenna aperture, radome, or transceiver on either path shall be autonomously detected and isolated so it does not degrade the still-functioning path.

## REQ-CTL-03: EMI/EMC control (Functional)
C&DH and terminal transceiver electronics shall meet conducted and radiated emissions/susceptibility limits to avoid interference with GNC, Safety, and each other's simultaneous RF operation.

## REQ-ENV-01: Antenna/radome thermal & vibroacoustic qualification (Functional)
Antenna apertures and radomes shall be qualified to withstand the induced thermal and vibroacoustic environment across ascent and reentry, including maintaining RF/optical transparency through peak reentry heating so the relay antenna remains functional.
