# GNC Requirements

## REQ-SYS-01: Closed-loop GNC function (Functional)
The GNC subsystem shall determine vehicle state, generate mission-phase guidance commands, compute control actions, and provide commands to the appropriate vehicle control-effectors through defined subsystem interfaces.

## REQ-SYS-02: Mission-phase applicability (Functional)
The GNC subsystem shall provide the functions and control authority required by the defined mission phase and active vehicle stage, including distinct Booster and Ship behavior after physical separation.

## REQ-SYS-03: Control-effectors boundary (Functional)
The GNC subsystem shall issue control demands through defined interfaces without assuming ownership of propulsion engines, thrust-vector actuators, RCS hardware, or aerodynamic control mechanisms owned by other subsystems.

## REQ-SYS-04: GNC state validity (Functional)
The GNC subsystem shall identify when the navigation/control state is unavailable, invalid, or degraded and shall provide the resulting status to the applicable GNC mode and health-management functions.

## REQ-NAV-01: Measurement processing (Functional)
NMP shall accept the defined navigation measurements, associate them with their valid timing/quality information, and provide a conditioned measurement set to the navigation estimator.

## REQ-NAV-02: Vehicle-state estimation (Functional)
NSE shall estimate the vehicle state variables required by the active guidance and control functions from the available validated measurements and navigation-aiding information.

## REQ-NAV-03: Navigation aiding integration (Functional)
NAI shall integrate each approved navigation-aiding source included in the architecture and shall make its information available to the state-estimation function with source validity information.

## REQ-NAV-04: Navigation integrity indication (Functional)
NVI shall provide an explicit navigation validity/degraded-state indication whenever the estimated state or an input measurement set does not satisfy the defined integrity criteria for the active GNC mode.

## REQ-GDN-01: Trajectory/reference selection (Functional)
GTR shall provide the active trajectory or reference definition required by the current mission phase and vehicle stage to the guidance function.

## REQ-GDN-02: Phase-dependent guidance (Functional)
GPH shall generate guidance commands appropriate to the active mission phase and vehicle stage using the current estimated state and active trajectory/reference information.

## REQ-GDN-03: Guidance constraints (Functional)
GCM shall apply the vehicle, mission, stage, and control-authority constraints allocated to the active guidance problem before issuing the guidance command.

## REQ-GDN-04: Guidance mode transition (Functional)
GMD shall transition between defined guidance modes only when the associated vehicle-state, mission-phase, and transition conditions are satisfied.

## REQ-CTL-01: Attitude/rate control (Functional)
CAT shall compute the rotational control demand required to track the commanded attitude and/or angular-rate state within the allocated control-performance limits.

## REQ-CTL-02: Translational/trajectory control (Functional)
CTR shall compute the translational control demand required to track the active guidance objective within the allocated vehicle-dynamics and control-authority limits.

## REQ-CTL-03: Control-mode management (Functional)
CAM shall select the applicable control regime and available control authority based on the active vehicle stage, mission phase, vehicle state, and actuator availability.

## REQ-CTL-04: Control demand limiting (Functional)
CLM shall prevent the control demand passed to command allocation from exceeding the applicable validated state, vehicle, or control-authority limits.

## REQ-CMD-01: Command shaping (Functional)
CAS shall transform the computed control demand into commands compatible with the defined command-interface limits, validity rules, and actuator/subsystem authority.

## REQ-CMD-02: Control allocation (Functional)
CAA shall allocate each aggregate control demand to the set of control-effectors authorized and available for the active vehicle stage and mission phase.

## REQ-CMD-03: Subsystem command routing (Functional)
CRS shall route each valid allocated control command to the defined receiving subsystem interface and shall identify a command as unavailable when its receiving path is not valid.

## REQ-FSW-01: GNC function execution (Functional)
FEX shall execute the allocated NAV, GDN, CTL, and CMD functions with the data dependencies and execution sequencing defined by the GNC architecture.

## REQ-FSW-02: Mode-state coordination (Functional)
FMG shall maintain the active GNC mode consistent with the vehicle stage, mission phase, navigation validity, control availability, and defined transition conditions.

## REQ-FSW-03: GNC data integrity and interface consistency (Functional)
FDB shall maintain the defined data identity, units, timing/validity metadata, and source/destination association for GNC data exchanged among the GNC functions and external subsystem interfaces.

## REQ-FSW-04: GNC-local health response (Functional)
FHM shall detect defined GNC-local health conditions and provide the resulting health/degraded-state information to the applicable GNC mode-management function and the external system-level safety/fault-management boundary.
