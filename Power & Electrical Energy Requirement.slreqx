# Power & Electrical Energy Requirement

## REQ-SYS-01: Electrical energy availability (Functional)
The Power & Electrical Energy subsystem shall make electrical energy available to each connected vehicle electrical load within the load's allocated operating limits and mission-phase availability requirements.

## REQ-SYS-02: Distributed fault isolation (Functional)
The subsystem shall provide fault isolation such that an electrical fault is prevented from propagating beyond its allocated isolation boundary while preserving unaffected electrical services to the extent permitted by the applicable fault case.

## REQ-SYS-03: Vehicle peak-power capability (Functional)
The vehicle electrical architecture represented by this subsystem shall be capable of supporting the published approximately 9 MW peak-power capability across Starship and Super Heavy without exceeding allocated electrical component and distribution limits.

## REQ-SYS-04: Mission-phase service (Functional)
The subsystem shall transition electrical-service availability and protection states as required by the defined mission phases without violating the allocated limits of connected loads.

## REQ-PES-01: Stored-energy source (Functional)
The energy-storage function shall provide the electrical energy required by the vehicle power architecture over each allocated operating condition and mission phase.

## REQ-PES-02: Battery-state observability (Functional)
The storage architecture shall provide the state and health information required by the power-management function to determine whether the available stored energy remains within its allocated operating envelope.

## REQ-PES-03: Storage isolation (Functional)
The storage architecture shall provide an isolation/protection function capable of disconnecting an affected storage path when an applicable electrical fault condition requires isolation.

## REQ-PCN-01: Power conversion (Functional)
The conversion function shall convert stored electrical energy into the electrical form required by the downstream vehicle power architecture within the allocated operating envelope.

## REQ-PCN-02: Conversion conditioning (Functional)
The power-conversion function shall condition its electrical output so that downstream distribution and connected loads receive power within their allocated electrical limits.

## REQ-PCN-03: Conversion-state monitoring (Functional)
The conversion architecture shall provide sufficient operating-state and health information to identify loss of conversion availability or operation outside allocated limits.

## REQ-HVD-01: High-voltage distribution (Functional)
The distribution architecture shall distribute high-voltage electrical power from the conversion/storage source to connected vehicle loads through the allocated protected distribution paths.

## REQ-HVD-02: Controlled isolation (Functional)
The distribution architecture shall provide controlled switching and isolation of electrical paths required to implement the defined nominal, maintenance, contingency, and fault-response states.

## REQ-HVD-03: Load-boundary protection (Functional)
The distribution architecture shall provide a protected electrical boundary for each connected load path such that an applicable load-side fault can be isolated without requiring loss of unrelated protected branches.

## REQ-HVD-04: Electrical protection status (Functional)
The distribution/protection architecture shall expose the state of applicable switching and isolation functions to the power-management and monitoring function.

## REQ-PMM-01: Power-state monitoring (Functional)
The power-management function shall maintain an internally consistent representation of electrical-source, conversion, distribution, and protection states needed for power-service decisions.

## REQ-PMM-02: Power-management coordination (Functional)
The power-management function shall coordinate source, conversion, distribution, and isolation states in accordance with the active mission phase and applicable fault-response logic.

## REQ-PMM-03: Protection-state reporting (Functional)
The power-management function shall report applicable protection and isolation states to the vehicle functions that require that information for safe operation or fault response.

## REQ-INT-01: Propulsion electrical service (Functional)
The Power subsystem shall provide the electrical service required by the Propulsion power interfaces defined in the project architecture, subject to each interface's allocated electrical limits and mission-phase activation.

## REQ-INT-02: Propellant-system electrical service (Functional)
The Power subsystem shall provide protected electrical service to the Propellant System's electrically powered functions through the allocated PowerIn boundary.

## REQ-INT-03: GNC electrical service (Functional)
The Power subsystem shall provide protected electrical service to the GNC subsystem's electrical loads through the allocated PowerIn boundary.

## REQ-INT-04: Communication electrical service (Functional)
The Power subsystem shall provide protected electrical service to the Communication subsystem's allocated C&DH/RF electrical loads through the interface defined in Section 07.

## REQ-INT-05: Thermal-protection electrical service (Functional)
The Power subsystem shall provide protected electrical service to the Thermal Protection monitoring/electrical loads represented by the existing TPS PowerIn dependency.

## REQ-INT-06: Structure & Mechanisms electrical service (Functional)
The Power subsystem shall provide protected electrical service to the Structure & Mechanisms actuator power boundary while leaving actuator mechanics and motion control ownership to Structure & Mechanisms.

## REQ-QAL-01: Electrical-model credibility (Functional)
Models used to demonstrate compliance of the Power subsystem with quantitative electrical requirements shall have documented verification, validation, uncertainty, and applicability evidence appropriate to the engineering decision being supported.
