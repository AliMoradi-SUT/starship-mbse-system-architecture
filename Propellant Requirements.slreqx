# Propellant Requirements

## REQ-SYS-01: Propellant load / delta-v margin (Functional)
Total loaded propellant shall meet the mission delta-v budget with defined margin.

## REQ-SYS-02: Mixture ratio loading accuracy (Functional)
Tanks shall be loadable to the target LOX:CH4 ratio within a defined tolerance, supporting Propulsion's engine mixture-ratio control.

## REQ-SYS-03: Propellant subsystem dry mass budget (Functional)
Total propellant subsystem dry mass (tanks, domes, plumbing, valves) shall not exceed the vehicle-level mass allocation.

## REQ-TNK-01: Propellant containment (Functional)
Tanks shall contain propellant without leakage across the full pressure/thermal range of all mission phases.

## REQ-TNK-02: Boil-off / thermal management (Functional)
Tanks shall limit propellant boil-off during prelaunch hold and coast to within the venting system's capacity.

## REQ-TNK-03: Landing/header tank capacity margin (Functional)
Header/landing tanks shall retain propellant margin for contingency scenarios (extended hover, divert).

## REQ-QAL-01: Tank structural strength & life (Functional)
Main and header tanks shall meet metallic pressure-vessel strength and life qualification margins.

## REQ-QAL-02: Common dome load path (Functional)
Common dome shall carry differential pressure and axial load between LOX and CH4 sections without failure.

## REQ-QAL-03: Downcomer/transfer tube structural integrity (Functional)
CH4 transfer tube shall withstand external crush pressure from the surrounding LOX column without buckling.

## REQ-QAL-04: COPV structural qualification (Functional)
Spin-start, igniter, and pneumatic actuation gas storage vessels shall meet composite overwrapped pressure vessel (COPV) safety-factor requirements.

## REQ-PRS-01: Autogenous pressurization control (Functional)
System shall maintain tank ullage pressure within Propulsion's turbopump inlet/NPSH requirements throughout powered flight.

## REQ-PRS-02: Purge & spin-start gas supply (Functional)
System shall supply spin-start and igniter gas to Propulsion at the pressure/flow required for each engine start event.

## REQ-PRS-03: Overpressure relief (Functional)
Venting system shall prevent tank pressure from exceeding maximum allowable working pressure under worst-case heating.

## REQ-FED-01: Feed flow rate & pressure (Functional)
Feed system shall deliver propellant to each engine's turbopump inlet within required flow rate and NPSH margin across throttle range.

## REQ-FED-02: Header tank switchover (Functional)
Feed system shall switch source between main and header/landing tanks without interrupting engine flow.

## REQ-VLV-01: Valve leak-tightness & cycle life (Functional)
Propellant, vent, and pressurization valves shall meet leak-tightness and cycle-life requirements for the qualified number of operations.

## REQ-GSE-01: Propellant loading rate (Functional)
Ground interface shall support loading both propellants within the countdown's allotted fill time.

## REQ-GSE-02: Propellant densification (Functional)
Ground interface shall deliver subcooled (densified) LOX and CH4 to increase loaded propellant mass for a given tank volume.

## REQ-GSE-03: Quick-disconnect release (Functional)
Ground umbilical shall cleanly disconnect at liftoff without damaging vehicle-side plumbing.

## REQ-CTL-01: Leak & anomaly detection (Functional)
System shall detect off-nominal tank pressure, level, or leak indications and report to Safety within a defined response time.

## REQ-CTL-02: Telemetry latency & bandwidth (Functional)
Tank telemetry shall be sampled/transmitted at a rate sufficient for GNC delta-v estimation and Safety anomaly response.

## REQ-ENV-01: Vibroacoustic & thermal qualification (Functional)
Tank-mounted valves, sensors, and controller electronics shall be qualified for the induced vibroacoustic and cryogenic thermal environment.
