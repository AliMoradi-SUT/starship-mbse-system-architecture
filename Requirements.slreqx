# Requirements

## REQ-SYS-01: Liftoff thrust-to-weight margin (Functional)
Liftoff thrust-to-weight ratio shall exceed vehicle gross liftoff weight by an adequate margin (typ. T/W ≥ 1.3).

## REQ-SYS-02: Engine-out mission continuation (Functional)
Subsystem shall maintain controllability and mission-continuation with ≥1 main engine failed at any powered-flight point.

## REQ-SYS-03: Delta-v performance budget (Functional)
Combined thrust × Isp × propellant mass shall meet the delta-v budget for the defined mission profile.

## REQ-ENG-01: Multi-restart capability (Functional)
Booster inner (gimbaling) engines and all ship main engines shall support ≥2 restarts per flight.

## REQ-QAL-01: Engine structural strength & life (Functional)
Main engine structural elements shall meet strength and life (fatigue/creep) qualification margins.

## REQ-QAL-02: Pressurized component safety factor (Functional)
Pressurized components shall meet metallic pressure vessel and COPV safety-factor requirements.

## REQ-QAL-03: Thrust mount & gimbal bearing safety factor (Functional)
Thrust mounts and the gimbal bearing shall meet minimum design and test factors of safety for structural load paths carrying full engine thrust.

## REQ-TVC-01: Gimbal control authority (Functional)
TVC shall null the maximum expected pitch and yaw disturbance torque with defined control margin. TVC provides no roll authority — roll is out of scope for this requirement (see REQ-ENG-02 for booster, REQ-RCS-01 for ship).

## REQ-TVC-02: Actuator torque margin (Functional)
TVC actuators shall maintain positive torque margin against maximum expected disturbance loads.

## REQ-RCS-01: RCS attitude control authority (ship only) (Functional)
Ship RCS shall provide full 3-axis attitude authority whenever main engines are off and aerosurfaces are ineffective, and shall provide roll-axis authority continuously — including during powered flight — since ship TVC provides pitch/yaw only. Booster carries no RCS; see REQ-ENG-02.

## REQ-RCS-02: RCS propellant budget margin (Functional)
RCS propellant allocation shall include margin above the nominal attitude-control budget to cover contingency maneuvers (e.g. extended coast, off-nominal separation).

## REQ-IGN-01: Ignition reliability (Functional)
Ignition system shall achieve reliable preburner light-off across the qualified inlet temperature / pressure range.

## REQ-VLV-01: Valve leak-tightness & cycle life (Functional)
Propellant valves shall meet leak-tightness and cycle-life requirements for the qualified number of starts.

## REQ-CTL-01: Autonomous fault detection & shutdown (Functional)
Engine controller shall detect off-nominal parameters and command safe shutdown within a defined response time.

## REQ-CTL-02: Telemetry latency & bandwidth (Functional)
Engine telemetry shall be sampled and transmitted at a rate sufficient for Safety and fault mgmt to detect and react to an anomaly within the response time required by REQ-CTL-01.

## REQ-SYS-04: Propulsion dry mass budget (Functional)
Total propulsion subsystem dry mass (engines, valves, controllers, TVC, RCS) shall not exceed the mass allocation set by the vehicle-level mass budget.

## REQ-ENV-01: Vibroacoustic qualification (Functional)
Engine- and TVC-mounted electronics (controllers, actuators) shall be qualified to withstand the random vibration and acoustic environment induced during powered flight.

## REQ-CTL-03: EMI/EMC contro (Functional)
Engine and RCS controller electronics shall meet conducted and radiated emissions/susceptibility limits to avoid interference with GNC and Communication.

## REQ-ENG-02: Booster roll control via differential throttle (Functional)
Booster shall achieve roll-axis control authority through coordinated differential throttling of engines offset from the roll axis (outer/inner ring); no booster engine gimbal contributes to roll, since gimbal deflection near the centerline produces negligible roll torque.
