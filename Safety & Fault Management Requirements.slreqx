# Safety & Fault Management Requirements

## REQ-SYS-01: System FDIR coverage (Functional)
The Safety & Fault Management subsystem shall provide the defined vehicle-level functions for health monitoring, fault detection, diagnosis, identification, isolation, response, recovery, and safety-state management across the applicable mission phases.

## REQ-SYS-02: Mission-phase applicability (Functional)
The Safety & Fault Management subsystem shall apply the fault-management and safety-state logic appropriate to the active vehicle stage and defined mission phase, including separate post-separation Booster and Ship safety states.

## REQ-SYS-03: Fault-containment coordination (Functional)
The subsystem shall coordinate responses intended to contain a detected fault to the allocated boundary and shall preserve unaffected vehicle functions to the extent permitted by the applicable fault case and defined safety response.

## REQ-HFD-01: Health evidence acquisition (Functional)
HIA shall acquire and associate each defined Safety-facing health/status input with its source, validity information, and applicable mission-state context before the evidence is used by downstream fault-management functions.

## REQ-HFD-02: Evidence validity evaluation (Functional)
VIE shall identify health/status information that is invalid, unavailable, stale, inconsistent, or otherwise outside its defined validity criteria and shall provide the resulting validity state to the applicable fault-management functions.

## REQ-HFD-03: Fault detection criteria (Functional)
FDE shall detect defined off-nominal conditions using the applicable threshold, range, persistence, consistency, status, or equivalent detection criteria allocated to each monitored fault case.

## REQ-HFD-04: Detection response-time allocation (Functional)
FDE shall detect each safety-significant fault within the allocated detection time established by the applicable hazard, failure-mode, or fault-management analysis.

## REQ-FDI-01: Fault correlation (Functional)
FCR shall correlate simultaneous or related fault indications using the defined dependency, timing, source-validity, and consistency information to reduce duplicate or contradictory fault interpretations.

## REQ-FDI-02: Fault isolation (Functional)
FIS shall isolate a detected fault to the finest level of architecture granularity supported by the available evidence and defined fault model, and shall explicitly identify when the fault cannot be isolated further.

## REQ-FDI-03: Fault classification (Functional)
FIC shall classify an identified or partially isolated fault according to the defined fault class, severity, confidence, and affected-function information required by the response-selection logic.

## REQ-FMR-01: Severity and consequence assessment (Functional)
SEA shall evaluate the severity and mission consequence of a detected fault using the applicable vehicle state, mission phase, affected function, available redundancy, and defined hazard/consequence information.

## REQ-FMR-02: Response selection (Functional)
RSL shall select a response consistent with the classified fault, safety state, mission phase, available recovery options, and approved response rules, including continuation, degraded operation, inhibit, shutdown, reconfiguration, or transition to a defined safe state where applicable.

## REQ-FMR-03: Protective-action coordination (Functional)
PAC shall issue only the defined vehicle-level safety commands to receiving subsystem interfaces and shall not assume ownership of the physical hardware that performs the commanded action.

## REQ-FMR-04: Response inhibit on insufficient evidence (Functional)
FMR shall prevent an automated safety response that requires confirmed fault evidence when the defined evidence-quality criteria are not satisfied, unless the applicable safety rule explicitly permits a fail-safe response to loss or invalidity of that evidence.

## REQ-RRM-01: Reconfiguration coordination (Functional)
RCO shall coordinate approved redundant-path selection, load shedding, inhibit, reset, shutdown, or other reconfiguration actions required by the selected fault response and shall track the requested configuration state.

## REQ-RRM-02: Recovery sequence execution (Functional)
RSE shall execute each approved recovery sequence in the defined order and shall prevent execution of a sequence when its required preconditions are not satisfied.

## REQ-RRM-03: Recovery verification (Functional)
RVF shall determine whether an approved recovery or reconfiguration action achieved its defined post-action state and shall report unsuccessful or indeterminate recovery to the safety-state and response functions.

## REQ-SFM-01: Safety-state management (Functional)
SSM shall maintain the vehicle-level safety state and shall permit transitions only through defined conditions associated with mission phase, detected faults, response outcomes, and applicable safety rules.

## REQ-SFM-02: Safe-state transition (Functional)
SSM shall command or coordinate transition to the approved safe state when the applicable fault condition and safety rule require escalation and the required response authority is available.

## REQ-SFM-03: Flight-safety coordination (Functional)
FSC shall provide the defined safety-state and flight-safety status information to the flight-safety boundary and shall coordinate authorized vehicle-level safety actions without asserting ownership of the AFSS internal implementation.

## REQ-SFM-04: Escalation and containment status (Functional)
ESC shall maintain the status of unresolved safety-significant faults, active containment actions, response completion, and residual degraded capability needed by the vehicle-level safety state.

## REQ-INT-01: Subsystem health interfaces (Functional)
HIA shall accept health and fault-status information from the defined Propulsion, Propellant System, Power & Electrical Energy, GNC, Communication, Thermal Protection, and Structure & Mechanisms endpoints without bypassing their subsystem ownership boundaries.

## REQ-INT-02: Protective command interfaces (Functional)
PAC shall send each approved safety command through the defined receiving-subsystem interface and shall identify the command outcome as accepted, rejected, unavailable, or indeterminate when that status is available from the interface.

## REQ-INT-03: Safety data traceability (Functional)
The Safety & Fault Management subsystem shall preserve the identity and validity association of safety-relevant fault, response, and state information sufficiently to support post-event analysis of the modeled fault-management behavior.
