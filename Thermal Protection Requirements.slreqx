# Thermal Protection Requirements

## REQ-SYS-01: Protected-structure temperature (Functional)
The Thermal Protection subsystem shall maintain the temperature of each protected structure or equipment item below its allocated maximum allowable temperature throughout each defined mission thermal environment.

## REQ-SYS-02: Mission thermal environments (Functional)
The Thermal Protection subsystem shall be assessed against the defined ascent, stage-separation, coast, reentry, and landing thermal environments applicable to each vehicle stage and protected region.

## REQ-SYS-03: Thermal margin (Functional)
The Thermal Protection subsystem shall maintain the approved thermal design margin between predicted or measured protected-item temperature and the applicable maximum allowable temperature for every mission-critical thermal case.

## REQ-STP-01: Ship TPS acreage protection (Functional)
STP-ACR shall provide the required thermal protection over each Starship primary TPS acreage region for the applicable reentry and other assigned high-heating environments without loss of required thermal function.

## REQ-STP-02: Ship base heat-shield protection (Functional)
STP-BHS shall limit heat transfer to protected hardware in the defined Starship base/plume thermal environments to within its allocated thermal limits.

## REQ-STP-03: Control-surface thermal protection (Functional)
STP-CTL shall protect the thermally exposed Starship control-surface regions and their adjacent interfaces against their defined aerodynamic heating environments while preserving the required control-surface function.

## REQ-BTP-01: Booster thermal protection (Functional)
BTP-ACR and BTP-BHS shall protect the defined thermally exposed Super Heavy regions against their applicable ascent, return, plume, and landing thermal environments within allocated limits.

## REQ-BTP-02: Forward interstage thermal protection (Functional)
BTP-FHI shall protect the applicable Super Heavy forward/interstage region from the thermal environment produced by Starship engine operation during stage separation for the vehicle configuration being modeled.

## REQ-TBI-01: Gap and seam protection (Functional)
TBI-GAP shall maintain the required thermal protection across defined TPS gaps, seams, and step transitions under their applicable aerothermal environments.

## REQ-TBI-02: Penetration and interface protection (Functional)
TBI-INT shall limit thermal intrusion at defined TPS penetrations, hatches, deployed-hardware interfaces, and TPS-to-structure interfaces to within allocated thermal limits.

## REQ-TBI-03: Discontinuity heating (Functional)
TBI-STP shall account for the increased local heating associated with defined TPS surface steps, protrusions, and other geometric discontinuities in the thermal analysis and qualification evidence.

## REQ-TMS-01: TPS temperature sensing (Functional)
TMS-SNS shall measure temperature at each Starship TPS monitoring location defined by the thermal-instrumentation architecture with the accuracy, range, sampling rate, and environmental qualification allocated to that sensor.

## REQ-TMS-02: Thermal-data integrity (Functional)
TMS-DAQ shall preserve the defined validity, timing, and traceability of TPS temperature measurements from acquisition through the thermal-state data output used by the vehicle model.

## REQ-TMS-03: Thermal-state observability (Functional)
TMS shall provide thermal-state data sufficient to correlate measured TPS temperatures with the thermal analysis cases and identify departures from the expected thermal response at the monitored locations.

## REQ-QAL-01: Thermal-model credibility (Functional)
The thermal analysis model used to demonstrate TPS compliance shall have documented verification, validation, uncertainty, and applicability evidence sufficient for the intended engineering decision.

## REQ-QAL-02: Representative thermal testing (Functional)
TPS qualification evidence shall include physical testing at representative thermal boundary conditions for each critical material/system behavior not adequately bounded by validated analysis.

## REQ-QAL-03: Flight-data correlation (Functional)
The TPS thermal model and predicted performance shall be correlated against available representative flight thermal measurements before the model is treated as validated for subsequent design decisions.
